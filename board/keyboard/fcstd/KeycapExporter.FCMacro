# KeycapExporter - http://github.com/harbaum/misterynano
#
# This FreeCAD Macro is meant to be used with the MiSTeryNano keycap designs. It allows to export
# STL files for printing and wrl files for kicad rendering. Multiple key of the same shape but with 
# different labels are exported from the same source.

import Mesh
import FreeCADGui

print("")
print("=====================")
print("   Keycap Exporter")
print("=====================")

# the KEYMAP descipbes which keys are to be generated from which design and gives
# some more informations on label positions and colors etc
KEYMAP = { 
	# Backspace, Help and Undo
	"help": {
		"basecolor": (0.8,0.8,0.8),
		"labelcolor": (0.3,0.3,0.3),
		"labels": [ "Undo", "←", "Help" ],
		"files": { "←": "backspace", "Help": "help", "Undo": "undo" },
		"sizes": { "←": 2 },
		"offsets": { "←": (0,.8,0) },
		"fonts": { "←": "/usr/share/fonts/truetype/dejavu/DejaVuSans-Bold.ttf" }
	},
	
	# F2 to F10 are derived from F1 and are bright grey on dark grey
	"F1": {
		"basecolor": (0.5,0.5,0.5),
		"labelcolor": (0.9,0.9,0.9),
		"labels": [  "F2", "F3", "F4", "F5", "F6", "F7", "F8", "F9", "F10", "F1" ] 
	},

	# numbers row
	"8": {
		"basecolor": (0.8,0.8,0.8),
		"labelcolor": (0.3,0.3,0.3),
		# the keypad star/( and ) include a trailing space to be distibguishable from the 8/star key
 		"labels": [ "Esc", [ "1","!" ], [ "2","@" ], [ "3","#" ], [ "4","$" ], [ "5","%" ], [ "6","^" ] , [ "7","&" ],
				[ "9","(" ], [ "0",")" ], ["-","_"], ["=","+"], ["`","~"], "( ", ") ", "/", "* ", [ "8","*" ] ],
		# some labels need to be resized so they are thick enough for 0.4mm printing
		"sizes": { "* ": 1.2, "*": 1.2, "@": 1.1, "^": 1.2, "_": 1.5, "-": 1.2, "`":1.3 ,"~":1.3 },
		"offsets": { "* ": (0,-1.5,0), "*": (0,-1.5,0), "^": (0,-1.5,0), "_": (0,1.5,0) },
		"files": { "Esc":"esc", "!":"1", "@":"2", "#":"3","$":"4", "%":"5","^":"6", "&":"7", "*":"8", "(":"9", ")":"0",
			"_":"minus", "+":"equal", "~":"accent",
			"( ":"kpopenbrace", ") ":"kpclosebrace", "/":"kpslash", "* ":"kpstar"  }, 
	},

	# top character row
	"U": {
		"basecolor": (0.8,0.8,0.8),
		"labelcolor": (0.3,0.3,0.3),
 		"labels": [  "Q", "W", "E", "R", "T", "Y", "I", "O", "P", ["[","{"], ["]","}"], "Del", "Ins", "↑" , "Clr", "7", "8", "9", "-", "U" ],
		# use modified file names for those that would be pure special char
		"files": { "[": "braceopen", "]": "braceclose", "↑":"up", "7":"kp7", "8":"kp8", "9":"kp9", "-":"kp-", "Del":"delete", "Ins":"insert", "Clr": "clrhome"}, 
		# some labels may need some positional adjustments to print nicely
		"offsets": { "{": (4,0,0), "}": (4,0,0), "[": (0,1,0), "]": (0,1,0), "↑":(0,-1,0) },
		# some labels need to be resized so they are thick enough for 0.4mm printing
		"sizes": { "↑": 2 },
		# some special chars are in different fonts
		"fonts": { "↑": "/usr/share/fonts/truetype/dejavu/DejaVuSans-Bold.ttf" }
	},

	# middle character row
	"D": {  # "↑"
		"basecolor": (0.8,0.8,0.8),
		"labelcolor": (0.3,0.3,0.3),
 		"labels": [  "A", "S", "F", "G", "H", "J", "K", "L", [";",":"], ["'",'"'], ["\\","|"],"←", "↓", "→", "4", "5", "6", "+", "D" ],
		# use modified file names for those that would be pure special char
		"files": { "←": "left", "↓": "down", "→": "right", "4":"kp4", "5": "kp5", "6": "kp6", "+": "kp+", 
			";": "semicolon", "'": "tick", "\\": "backslash" },
		# some labels may need some positional adjustments to print nicely
		"offsets": { "J": (1,0,0), "←": (0,0,0) , "↓":(0,-1,0), "→":(0,0,0), ":":(0,1,0), ";":(0,1,0), "\\":(0,0,0) , "|":(2,0,0) },
		# some labels need to be resized so they are thick enough for 0.4mm printing
		"sizes": { "←":2 , "↓":2, "→":2},
		# some special chars are in different fonts
		"fonts": { "←": "/usr/share/fonts/truetype/dejavu/DejaVuSans-Bold.ttf",
		           "↓": "/usr/share/fonts/truetype/dejavu/DejaVuSans-Bold.ttf" ,
		           "→": "/usr/share/fonts/truetype/dejavu/DejaVuSans-Bold.ttf" }
	},

	# bottom character row
	"V": { 
		"basecolor": (0.8,0.8,0.8),
		"labelcolor": (0.3,0.3,0.3),
 		"labels": [  "Z", "X", "C", "B", "N", "M", [ ",","<"], [".",">"], ["/","?"], "1", "2", "3", "☰", "V" ] ,
		# use modified file names for those that would be pure special char
		"files": { ",": "comma" , ".": "dot", "/": "slash", "1":"kp1", "2": "kp2", "3": "kp3", "☰": "intl" },
		# some labels may need some positional adjustments to print nicely
		"offsets": { ",": (0,1.5,0), ".": (0,1.5,0) , "/": (1,0,0), "☰": (0,-1,0) },
		# some labels need to be resized so they are thick enough for 0.4mm printing
		"sizes": { "<": 1.1, ">": 1.1, "☰": 2 },
		# some special chars are in different fonts
		"fonts": { "☰": "/usr/share/fonts/truetype/dejavu/DejaVuSans-Bold.ttf" }
	},

	# bottom row
	"alternate": {
		"basecolor": (0.8,0.8,0.8),
		"labelcolor": (0.3,0.3,0.3),
 		"labels": [  "Alt", "Caps" ],
		# use modified file names for those that would be pure special char
		"files": { "Alt": "alternate", "Caps": "capslock" },
	}

}

def export_key_with_label(doc, keymap, label):
	if not label:
		# no label given, so use the one of the doc itself
		filebase = doc.Label
	else:
		# label may be an array of multiple labels if a bottom
		# label is to be used
		if isinstance(label, list):
			labelBottom = label[0]
			label = label[1]
		else:
			labelBottom = None		

		filebase = label
		# check if any of the labels is in the list of filesnames to use instead
		if "files" in keymap:
			if label in keymap["files"]:
				filebase = keymap["files"][label]
			elif labelBottom in keymap["files"]:
				filebase = keymap["files"][labelBottom]

		oldPlace = []
		oldSize = []
		oldFont = []

		# modify main (top) label
		labelObj = doc.getObjectsByLabel("ShapeString")
		for l in labelObj:
			l.String = label
	
			# check if the size is to be adjusted
			if "sizes" in keymap and label in keymap["sizes"]:
				oldSize.append([l, l.Size])
				l.Size *= keymap["sizes"][label]

			# check if the font is to be adjusted
			if "fonts" in keymap and label in keymap["fonts"]:
				oldFont.append([l, l.FontFile])
				l.FontFile = keymap["fonts"][label]

			# check if this label needs a position fix
			if "offsets" in keymap and label in keymap["offsets"]:
				oldPlace.append( [l,l.Placement.Base ])
				l.Placement.Base += FreeCAD.Base.Vector(keymap["offsets"][label])

		# modify or hide (set to "") secondary (bottom) label
		labelBotObj = doc.getObjectsByLabel("ShapeStringBottom")
		for l in labelBotObj:
			if labelBottom:
				# check if the size is to be adjusted
				if "sizes" in keymap and labelBottom in keymap["sizes"]:
					oldSize.append([l, l.Size])
					l.Size *= keymap["sizes"][labelBottom]

				l.String = labelBottom

				# check if this label needs a position fix
				if "offsets" in keymap and labelBottom in keymap["offsets"]:
					oldPlace.append( [l,l.Placement.Base ])
					l.Placement.Base += FreeCAD.Base.Vector(keymap["offsets"][labelBottom])
			else:
				oldPlace.append( [l,l.Placement.Base ])
				# setting the label to something white _does_ not hide it at
				l.Placement.Base.z += 10
				l.String = "X"

		doc.recompute()

	# export base and label to STL
	baseObj = None
	labelObj = None
	for obj in doc.Objects:
		# print("Type:", obj.TypeId, "Name",  obj.Name, "label", obj.Label)

		# check for object labeled "Base"
		if obj.Label == "Base":
			if baseObj: print("Warning, multiple Base objects")
			baseObj = obj
			filename = u"./stl/"+filebase+"-"+obj.Label+".stl"
			print("Exporting", filename)
			Mesh.export([obj], filename)

		if obj.Label == "Label":
			if labelObj: print("Warning, multiple Label objects")
			labelObj = obj
			filename = u"./stl/"+filebase+"-"+obj.Label+".stl"
			print("Exporting", filename)
			Mesh.export([obj], filename)

	# if there was a base and a label, then export them together to wrl for
 	# use in kicad
	if baseObj and labelObj:
		# the colors are stored in the GUI doc		
		gbase = Gui.getDocument(docName).getObject(baseObj.Name)		
		glabel = Gui.getDocument(docName).getObject(labelObj.Name)		

		# use keypmap colors if present, otherwise use defaul
		if keymap and "basecolor" in keymap: gbase.ShapeColor = keymap["basecolor"]
		else: gbase.ShapeColor = (0.8,0.8,0.8)
		if keymap and "labelcolor" in keymap: glabel.ShapeColor = keymap["labelcolor"]
		else: glabel.ShapeColor = (0.3,0.3,0.3)

		filename = u"./wrl/"+filebase+".wrl"
		print("Exporting", filename)
		FreeCADGui.export([baseObj, labelObj], filename)
	elif baseObj:
		# only base object, no labels (e.g. spacebar)
		gbase = Gui.getDocument(docName).getObject(baseObj.Name)		
		gbase.ShapeColor = (0.8,0.8,0.8)
		filename = u"./wrl/"+filebase+".wrl"
		print("Exporting", filename)
		FreeCADGui.export([baseObj], filename)

	# undo movement of bottom label
	if keymap and (oldPlace or oldSize or oldFont):
		for i in oldPlace:i[0].Placement.Base = i[1]
		for i in oldSize:i[0].Size = i[1]
		for i in oldFont:i[0].FontFile = i[1]
		doc.recompute()

# get all documents as these are the keys
for docName in App.listDocuments():
	docLabel = App.getDocument(docName).Label

	print("Processing key", docLabel)

	if docLabel in KEYMAP:
		keymap = KEYMAP[docLabel]

		# Export all variants with modified label ...
		for label in keymap["labels"]:
			export_key_with_label(App.getDocument(docName), keymap, label)
	else:
		print("Unknown key, exporting as it is")
		export_key_with_label(App.getDocument(docName), None, None)
